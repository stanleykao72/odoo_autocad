; Read CSV  -  Lee Mac
;; Parses a CSV file into a matrix list of cell values.
;; csv - [str] filename of CSV file to read
(defun LM:readcsv ( csv / des lst sep str )
    (if (setq des (open csv "r"))
        (progn
            (setq sep (cond ((vl-registry-read "HKEY_CURRENT_USER\\Control Panel\\International" "sList")) (",")))
            (while (setq str (read-line des))
                (setq m (strlen str))
                (if (> m 0)
                  (progn
                      (setq lst (cons (LM:csv->lst str sep 0) lst))
                  )
                  
                )
            )
            (close des)
        )
    )
    ;(reverse lst)
    lst
)
;; CSV -> List  -  Lee Mac
;; Parses a line from a CSV file into a list of cell values.
;; str - [str] string read from CSV file
;; sep - [str] CSV separator token
;; pos - [int] initial position index (always zero)
(defun LM:csv->lst ( str sep pos / s )
    (cond
        (   (not (setq pos (vl-string-search sep str pos)))
            (if (wcmatch str "\"*\"")
                (list (LM:csv-replacequotes (substr str 2 (- (strlen str) 2))))
                (list str)
            )
        )
        (   (or (wcmatch (setq s (substr str 1 pos)) "\"*[~\"]")
                (and (wcmatch s "~*[~\"]*") (= 1 (logand 1 pos)))
            )
            (LM:csv->lst str sep (+ pos 2))
        )
        (   (wcmatch s "\"*\"")
            (cons
                (LM:csv-replacequotes (substr str 2 (- pos 2)))
                (LM:csv->lst (substr str (+ pos 2)) sep 0)
            )
        )
        (   (cons s (LM:csv->lst (substr str (+ pos 2)) sep 0)))
    )
)
(defun LM:csv-replacequotes ( str / pos )
    (setq pos 0)
    (while (setq pos (vl-string-search  "\"\"" str pos))
        (setq str (vl-string-subst "\"" "\"\"" str pos)
              pos (1+ pos)
        )
    )
    str
)
(defun vk_WriteTextStream (Stream FileName Charset / ADODBStreamObj Result)
  (if (setq ADODBStreamObj (vlax-create-object "ADODB.Stream"))
    (progn (setq Result	(vl-catch-all-apply
			  (function
			    (lambda ()
			      (vlax-put ADODBStreamObj "Charset" Charset)
			      (vlax-invoke ADODBStreamObj "Open")
			      (vlax-invoke-method ADODBStreamObj "WriteText" Stream 0)
			      (vlax-invoke ADODBStreamObj "SaveToFile" FileName 2)
			    )
			  )
			)
	   )
	   (vlax-release-object ADODBStreamObj)
	   (if (not (vl-catch-all-error-p Result))
	     FileName
	   )
    )
  )
)
;;;(vk_WriteTextStream "??????? ??????? ?? ??????" "C:\\Temp\\test.txt" "utf-8")
(defun vk_ReadTextStream (FileName Charset / ADODBStreamObj Result)
  (if (and (setq FileName (findfile FileName))
	   (setq ADODBStreamObj (vlax-create-object "ADODB.Stream"))
      )
    (progn (setq Result	(vl-catch-all-apply
			  (function
			    (lambda ()
			      (vlax-put ADODBStreamObj "Charset" Charset)
			      (vlax-invoke ADODBStreamObj "Open")
			      (vlax-invoke ADODBStreamObj "LoadFromFile" FileName)
			      (vlax-invoke-method ADODBStreamObj "ReadText" -1)
			    )
			  )
			)
	   )
	   (vlax-release-object ADODBStreamObj)
	   (if (not (vl-catch-all-error-p Result))
	     Result
	   )
    )
  )
)
;;;(vk_ReadTextStream "C:\\Temp\\test.txt" "utf-8")
(defun UTF_Convert (FileName1 Codek1 FileName2  Codek2 / SuchenErsetzen StringOrg StringNew f Inhalt)
  (setq Codek1 (strcase Codek1) 
        Codek2 (strcase Codek2)
  )
  (if (= Codek1 "ANSI")
    (progn 
      (setq f (open FileName1 "r"))
      (setq StringOrg (read-line f))
      (while (setq Inhalt (read-line f ))
        (princ Inhalt )
        (setq StringOrg (strcat StringOrg "\n" Inhalt  ))
      )
      (close f)
    );progn
    (setq StringOrg (vk_ReadTextStream FileName1 Codek1 ))
  );if
  (if (or (vl-string-search Codek1 StringOrg )(vl-string-search "WINDOWS-1252" StringOrg )(vl-string-search "windows-1252" StringOrg ))
    (progn 
      (cond ((vl-string-search "WINDOWS-1252" StringOrg ) (setq StringNew (vl-string-subst Codek2 "WINDOWS-1252" StringOrg )))
            ((vl-string-search "windows-1252" StringOrg ) (setq StringNew (vl-string-subst Codek2 "windows-1252" StringOrg )))
            ((= Codek2 "ANSI" ) (setq StringNew (vl-string-subst "WINDOWS-1252" Codek1 StringOrg )))
            ((vl-string-search Codek1 StringOrg ) (setq StringNew (vl-string-subst Codek2 Codek1 StringOrg )))
            (t nil)
      )
    )
    (progn 
      ;(princ "\n Codek not found in file! " )
      (setq StringNew StringOrg )
    )
  )
  (if (= Codek2 "ANSI")
    (progn 
      (setq f (open FileName2 "w"))
      (write-line StringNew f)
      (close f)
    )
    (vk_WriteTextStream StringNew FileName2 Codek2 )
  )
)
